FME workspace zadanie3.fmw

Parameters:
- DestDataset_FILEGDB =
- DestDataset_POSTGIS_RASTER =
- DestDataset_POSTGIS_RASTER_3 =
- SourceDataset_GEOTIFF =
- SourceDataset_OGCGEOPACKAGE =

Readers:
- OGCGEOPACKAGE_1: OGCGEOPACKAGE from $(SourceDataset_OGCGEOPACKAGE)
- GEOTIFF_1: GEOTIFF from $(SourceDataset_GEOTIFF)

Writers:
- FILEGDB_1: FILEGDB to $(DestDataset_FILEGDB)
- POSTGIS_RASTER_1: POSTGIS_RASTER to $(DestDataset_POSTGIS_RASTER)
- POSTGIS_RASTER_2: POSTGIS_RASTER to $(DestDataset_POSTGIS_RASTER_3)

scotland_and_wales_region (reader OGCGEOPACKAGE_1)
    attributes: Name text(100), Area_Code text(3), Area_Description text(50), File_Name text(100), Feature_Serial_Number mediumint, Collection_Serial_Number mediumint, Global_Polygon_ID mediumint, Admin_Unit_ID mediumint, Census_Code text(9), Hectares double, Non_Inland_Area double, Area_Type_Code text(2), Area_Type_Description text(25), Non_Area_Type_Code text(3), Non_Area_Type_Description text(36), fid int,PrimaryKey
    -> AttributeFilter
AttributeFilter
    ATTR_NAME = Area_Code
    ATTR_VALUES = <Empty>,<Missing>,<Null>,<Unfiltered>,WPE
    WPE -> TestFilter
TestFilter
    DEFAULT_VALUE = <UNFILTERED>
    TEST_LIST = "BOOL_OP,OR,COMPOSITE_TEST,""""""1"""""",TEST_CLAUSE,TEST @Value(Feature_Serial_Number) < 1629",@Value(Feature_Serial_Number) < 1629
    @Value(Feature_Serial_Number) < 1629 -> FeatureJoiner [LEFT]
    @Value(Feature_Serial_Number) < 1629 -> Clipper [CLIPPER]
GEOTIFF (reader GEOTIFF_1)
    -> Reprojector
    -> RasterExtentsCoercer
    -> FeatureJoiner_3 [LEFT]
    -> FeatureJoiner_2 [LEFT]
Reprojector
    DEST = EPSG:4326
    INTERPOLATION_TYPE_NAME = Nearest Neighbor
    RASTER_CELL_SIZE = Preserve Cells
    RASTER_TOLERANCE = 0.0
    REPROJECTED -> RasterPropertyExtractor
RasterPropertyExtractor
    -> AttributeCreator
AttributeCreator
    ATTR_TABLE = SET_TO sciezka = $(FME_MF_DIR_ENCODED)ras250_gb\data\@Value(fme_basename).tif
    -> FilePropertyExtractor
FilePropertyExtractor
    FMT = FME Date/Time (%Y%m%d%H%M%S)
    PATH = @Value(sciezka)
    -> AttributeCreator_2
AttributeCreator_2
    ATTR_TABLE = SET_TO NewName = @Value(fme_basename)_@Value(_file_size)
    -> Extents (writer FILEGDB_1)
Extents (writer FILEGDB_1)
    attributes: NewName text(200), sciezka text(200), _num_bands double, _num_rows double, _num_columns double, _spacing_x double, _spacing_y double, _origin_x double, _origin_y double, _rotation_x double, _rotation_y double, _min_x double, _min_y double, _max_x double, _max_y double, _cell_origin_x double, _cell_origin_y double, _upper_left_x double, _upper_left_y double, _upper_right_x double, _upper_right_y double, _lower_right_x double, _lower_right_y double, _lower_left_x double, _lower_left_y double, _file_type text(2048), _file_size text(2048), _file_atime text(2048), _file_mtime text(2048), _file_ctime text(2048)
RasterExtentsCoercer
    EXTENTS_TYPE = Raster Extents
    EXTENTS -> FeatureJoiner [RIGHT]
    EXTENTS -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> UniqueValueLogger_2
UniqueValueLogger_2
    VAL = @Value(fme_basename)
    -> FeatureJoiner_3 [RIGHT]
    -> Clipper_2 [CLIPPER]
FeatureJoiner_3
    ATTR_CONFLICT_RES = Use Left
    GEOMETRY_HANDLING = Use Left
    JOIN_KEYS = fme_basename _value AUTO
    JOIN_MODE = Inner
    JOINED -> Clipper_2 [CLIPPEE]
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> RasterPaletteResolver
RasterPaletteResolver
    -> Exports (writer POSTGIS_RASTER_1)
Exports (writer POSTGIS_RASTER_1)
    attributes: _count int8, _value varchar(200), _clipped char(3)
FeatureJoiner
    ATTR_CONFLICT_RES = Use Left
    GEOMETRY_HANDLING = Use Left
    JOIN_KEYS = Name fme_basename AUTO
    JOIN_MODE = Full
    JOINED -> AreaOnAreaOverlayer [AREA]
AreaOnAreaOverlayer
    ACCUM_ATTRS_NAME = Use Attributes From One Feature
    CLEANING_TOLERANCE = Automatic
    CONNECT_Z_MODE = First Wins
    DEAGGREGATE_INPUT = Yes
    OVC_ATTR = _overlaps
    AREA -> Tester
Tester
    BOOL_OP = OR
    COMPOSITE_TEST = 1
    TEST_CLAUSE = TEST @Value(_overlaps) > 1
    TEST_MODE = TEST
    PASSED -> UniqueValueLogger
UniqueValueLogger
    VAL = @Value(fme_basename)
    -> FeatureJoiner_2 [RIGHT]
    -> Clipper_3 [CLIPPER]
FeatureJoiner_2
    ATTR_CONFLICT_RES = Use Left
    GEOMETRY_HANDLING = Use Left
    JOIN_KEYS = fme_basename _value AUTO
    JOIN_MODE = Inner
    JOINED -> Clipper_3 [CLIPPEE]
Clipper_3
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> RasterPaletteResolver_2
RasterPaletteResolver_2
    -> Exports (writer POSTGIS_RASTER_2)
Exports (writer POSTGIS_RASTER_2)
    attributes: _count int8, _value varchar(200), _clipped char(3)

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =

Input (input)
    -> AttributeCreator

Bookmark: Count unique attribute values
AttributeCreator
    ATTR_TABLE = SET_TO _value = $(VAL)
    -> AttributeKeeper
Note: Remove unwanted / attributes
AttributeKeeper
    CREATE_BULK_MODE_FEATURES = No
    KEEP_ATTRS = _value
    -> Aggregator
Note: Create aggregates of / features, grouped by / the target attribute value
Aggregator
    ACCUM_ATTRS_NAME = Merge Incoming Attributes
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO

FME custom transformer FilePropertyExtractor
Extracts basic properties of a file or a directory and adds these attributes to the feature.
    _file_type
    : holds "File" or "Directory", which indicates whether the specified path is a file or a directory.
    _file_size
    : holds the size of file/directory in bytes (total of file sizes if directory)
    _file_atime
    : holds the time of last access.
    _file_mtime
    : holds the time of last modification.
    _file_ctime
    : holds the time of creation on some systems (like Windows), or the time of last metadata change on other systems (like Unix).
    You can specify the format of "_file_atime", "_file_mtime", and "_file_ctime" via the "Date/Time Format" parameter.
    The input feature will be output from the 
    <Rejected>
    port if the specified file/directory does not exist, the path indicates a symbolic link, or an unexpected error has occurred. 
    This transformer contains a Python script, which was tested with both Python 2.7 and Python 3.4 interpreter.
Parameters
    File/Directory Path
    :
    Specify the path of a file or a directory.
    Date/Time Format
    :
    Specify a date/datetime/time format that should be applied to the values of "_file_atime", "_file_mtime", and "_file_ctime". 
    The format syntax is the same as the DateFormatter. See the help doc on the transformer.

Parameters:
- FMT =
- PATH =

Input (input)
    -> ParameterFetcher
ParameterFetcher
    ATTR_LIST = __filepropertyextractor.path {$(PATH)}
    -> PythonCaller
PythonCaller
    NEW_ATTRIBUTES = _file_type _file_size _file_atime _file_mtime _file_ctime __filepropertyextractor.error
    PYTHONSOURCE:
      # 2016-05-25, Takashi Iijima, Original Implementation
      # 2020-01-28, Takashi Iijima, Calculate Directory Size as Total File Sizes under the Directory; Changed Default Python Interpreter to 3.6+

      import fme, fmeobjects
      import os
      def extractFileProperty(feature):
          def get_dir_size(path):
              total = 0
              for p in os.listdir(path):
                  full_path = os.path.join(path, p)
                  if os.path.isfile(full_path):
                      total += os.path.getsize(full_path)
                  elif os.path.isdir(full_path):
                      total += get_dir_size(full_path)
              return total
          try:
              path = feature.getAttribute('__filepropertyextractor.path')
              if os.path.exists(path) and not os.path.islink(path):
                  s = os.stat(path)
                  if os.path.isdir(path):
                      feature.setAttribute('_file_type', 'Directory')
                      feature.setAttribute('_file_size', get_dir_size(path))
                  else:
                      feature.setAttribute('_file_type', 'File')
                      feature.setAttribute('_file_size', s.st_size)
                  feature.setAttribute('_file_atime', int(s.st_atime))
                  feature.setAttribute('_file_mtime', int(s.st_mtime))
                  feature.setAttribute('_file_ctime', int(s.st_ctime))
              else:
                  raise Exception('specified file/directory does not exist')
          except Exception as ex:
              feature.setAttribute('__filepropertyextractor.error', '%s' % ex)
    PYTHONSYMBOL = extractFileProperty
    -> Tester
Tester
    BOOL_OP = OR
    TEST_CLAUSE = TEST __filepropertyextractor.error ATTRIBUTE_IS_MISSING ""
    TEST_MODE = Automatic
    PASSED -> AttributeRemover
    FAILED -> AttributeRemover_2
AttributeRemover
    REMOVE_ATTRS = __filepropertyextractor.path,__filepropertyextractor.error
    -> DateFormatter
DateFormatter
    DATE_ATTR = _file_ctime,_file_mtime,_file_atime
    FMT = $(FMT)
    INVALID_DATE_VALUE = _FME_NO_OP_
    SRCFMT = %s
    -> Output (output)
Output (output)
AttributeRemover_2
    REMOVE_ATTRS = _file_size,_file_type,_file_ctime,__filepropertyextractor.path,_file_mtime,_file_atime
    -> AttributeRenamer
AttributeRenamer
    ATTR_TABLE = RENAME_SET_DEFAULT __filepropertyextractor.error > _rejected_reason
    -> <Rejected> (output)
<Rejected> (output)
